--
-- $Id: Conference-Add-On-Operations.asn 54539 2014-01-01 18:02:11Z wmeier $
--
-- EN 300 185-1 Ver. 1.2.4
--
Conference-Add-On-Operations {ccitt identified-organization etsi (0) 185 operations-and-types (1)}

DEFINITIONS EXPLICIT TAGS ::=
BEGIN

EXPORTS			BeginCONF, AddCONF, SplitCONF, DropCONF,
				IsolateCONF, ReattachCONF, PartyDISC,
				IllConferenceId, IllPartyId,
				NumberOfPartiesExceeded,
				NotActive, NotAllowed, PartyId, ConferenceId, ConfSize;

IMPORTS		OPERATION,
				ERROR
				FROM Remote-Operations-Information-Objects 
    {joint-iso-itu-t (2) remote-operations (4) informationObjects(5) version1(0)}
				notSubscribed, notAvailable,
				supplementaryServiceInteractionNotAllowed,
				resourceUnavailable, invalidCallState
				FROM General-Errors
					{ccitt identified-organization etsi(0) 196 general-errors (2)};

beginCONF		OPERATION ::= {
				ARGUMENT	BeginCONFArg  -- optional
				RESULT	BeginCONFRes
				ERRORS	{notSubscribed | notAvailable |
						resourceUnavailable |
						invalidCallState |
						numberOfPartiesExceeded}
     			CODE        local:  40}

BeginCONFArg ::= ConfSize

BeginCONFRes ::= SEQUENCE {
							conferenceId ConferenceId,
							partyId PartyId OPTIONAL }

addCONF 		OPERATION ::= {
				ARGUMENT	AddCONFArg 
				RESULT	AddCONFRes 
				ERRORS	{IllConferenceId |
						NumberOfPartiesExceeded |
						NotAllowed |
						supplementaryServiceInteractionNotAllowed |
						invalidCallState}
				CODE        local:  41}

AddCONFArg ::= ConferenceId
AddCONFRes ::= PartyId

splitCONF 	OPERATION  ::= {
				ARGUMENT	SplitCONFArg
				RETURN RESULT     FALSE
				ERRORS	{IllConferenceId | IllPartyId}
				CODE        local:  42}


SplitCONFArg ::= SEQUENCE { conferenceId	ConferenceId,
						partyId	PartyId}

dropCONF		OPERATION ::= {
				ARGUMENT	DropCONFArg
				RETURN RESULT     FALSE
				ERRORS	{IllPartyId, NotActive}
				CODE        local:  43}

DropCONFArg ::= PartyId

isolateCONF		OPERATION ::= {
				ARGUMENT	IsolateCONFArg
				RETURN RESULT     FALSE
				ERRORS 	{IllPartyId, NotActive}
				CODE        local:  44}

IsolateCONFArg  ::= PartyId

reattachCONF 	OPERATION ::= {
				ARGUMENT	ReattachCONFArg
				RETURN RESULT     FALSE
				ERRORS	{IllPartyId, NotActive}
				CODE        local:  45}

ReattachCONFArg ::= PartyId

partyDISC		OPERATION ::= {
				ARGUMENT	PartyDISCArg
				RETURN RESULT     FALSE
				CODE        local:  46}

PartyDISCArg ::= PartyId

--IllConferenceId 		::=	ERROR
illConferenceId  ERROR ::= { CODE  local: 28}
--IllPartyId 				::=	ERROR
illPartyId  ERROR ::= { CODE  local: 29}
--NumberOfPartiesExceeded	::=	ERROR
numberOfPartiesExceeded  ERROR ::= { CODE  local: 30}
--NotActive				::=	ERROR
notActive  ERROR ::= { CODE  local: 31}
--NotAllowed				::=	ERROR
notAllowed  ERROR ::= { CODE  local: 32}

PartyId					::=	INTEGER (0..127)
ConferenceId			::=	INTEGER (0..127)
ConfSize 				::=	INTEGER (0..127)

--beginCONF				BeginCONF				::= 40
--addCONF					AddCONF					::= 41
--splitCONF				SplitCONF				::= 42
--dropCONF				DropCONF				::= 43
--isolateCONF				IsolateCONF				::= 44
--reattachCONF			ReattachCONF			::= 45
--partyDISC				PartyDISC				::= 46
--illConferenceId			IllConferenceId			::= 28
--illPartyId				IllPartyId				::= 29
--numberOfPartiesExceeded	NumberOfPartiesExceeded	::= 30
--notActive				NotActive				::= 31
--notAllowed				NotAllowed				::= 32

END -- of Conference-Add-On-Operations
